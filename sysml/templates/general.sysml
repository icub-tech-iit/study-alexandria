part GENERAL {
	attribute folder_name : String default "./";
	attribute skipCalibration : Boolean default false;
	attribute useRawEncoderData : Boolean default false;
    attribute useLimitedPWM : Boolean default false;
	attribute verbose : Boolean default false;
}
