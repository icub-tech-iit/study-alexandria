part PC104 {
	attribute folder_name : String default "hardware/electronics/";
	attribute PC104IpAddress : String default "10.0.1.104";
	attribute PC104IpPort : Integer default 12345;
    attribute PC104TXrate : Integer default 1;
	attribute PC104RXrate : Integer default 5;
}
